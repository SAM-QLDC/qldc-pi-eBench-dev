FME workspace eBench B tsdata.fmw

Parameters:
- DestDataset_REDSHIFT =
- end_date =
- password =
- start_date =
- url =
- username =

Writers:
- REDSHIFT_1: REDSHIFT to $(DestDataset_REDSHIFT)

Note: automation / parameters to automate the pull in of tsdata
Note: tokens / create tokens for each council area / note: we don;t have GW data
Note: time series data
Note: read values from csv
Note: output

Bookmark: automation
Creator_2
    GEOMTYPE = Geometry Object
    NUM = 1
    CREATED -> AttributeCreator_3
AttributeCreator_3
    ATTR_TABLE:
      SET_TO _join = 1
      SET_TO start_date = $(start_date)
      SET_TO end_date = $(end_date)
      SET_TO start = @DateTimeFormat(@Value(start_date),%Y-%m-%d)
      SET_TO end = @DateTimeFormat(@Value(end_date),%Y-%m-%d)
    -> FeatureJoiner_3 [LEFT]
Creator_3
    GEOMTYPE = Geometry Object
    NUM = 3
    CREATED -> AttributeCreator_5
AttributeCreator_5
    ATTR_TABLE:
      SET_TO _join = 1
      SET_TO data_label = FME_CONDITIONAL:DEFAULT_VALUE'_FME_NO_OP_'BOOL_OP;OR;COMPOSITE_TEST;1;TEST @Value(_creation_instance) = 0'Total Energy - CO2e'BOOL_OP;OR;COMPOSITE_TEST;1;TEST @Value(_creation_instance) = 1'Total Energy - kWh'BOOL_OP;OR;COMPOSITE_TEST;1;TEST @Value(_creation_instance) = 2'Total Energy - $'FME_NUM_CONDITIONS4___
      SET_TO data_unit = FME_CONDITIONAL:DEFAULT_VALUE'_FME_NO_OP_'BOOL_OP;OR;COMPOSITE_TEST;1;TEST @Value(_creation_instance) = 0'kg'BOOL_OP;OR;COMPOSITE_TEST;1;TEST @Value(_creation_instance) = 1'kWh'BOOL_OP;OR;COMPOSITE_TEST;1;TEST @Value(_creation_instance) = 2'$'FME_NUM_CONDITIONS4___
      SET_TO data_source = standard
      SET_TO data_type = FME_CONDITIONAL:DEFAULT_VALUE'_FME_NO_OP_'BOOL_OP;OR;COMPOSITE_TEST;1;TEST @Value(_creation_instance) = 0'co2'BOOL_OP;OR;COMPOSITE_TEST;1;TEST @Value(_creation_instance) = 1'cons'BOOL_OP;OR;COMPOSITE_TEST;1;TEST @Value(_creation_instance) = 2'cost'FME_NUM_CONDITIONS4___
    -> FeatureJoiner_3 [RIGHT]
FeatureJoiner_3
    ATTR_CONFLICT_RES = Use Left
    GEOMETRY_HANDLING = Use Left
    JOIN_KEYS = _join _join AUTO
    JOIN_MODE = Inner
    JOINED -> AttributeRemover
AttributeRemover
    REMOVE_ATTRS = _creation_instance,end_date,start_date
    -> Tester_2
Note: only interested in kWh for now
Tester_2
    BOOL_OP = OR
    COMPOSITE_TEST = 1
    TEST_CLAUSE = TEST @Value(data_label) = Total Energy - kWh
    TEST_MODE = TEST
    PASSED -> Junction
Junction
    -> Junction_2

Bookmark: time series data
Junction_2
    -> FeatureJoiner [LEFT]
Junction_4
    -> AttributeKeeper_4
AttributeKeeper_4
    CREATE_BULK_MODE_FEATURES = NO
    KEEP_ATTRS = GetToken,org_id,siteid
    -> DuplicateFilter
DuplicateFilter
    INPUT_ORDERED_CHOICE = No
    KEYATTR = GetToken org_id siteid
    UNIQUE -> Aggregator
Aggregator
    ACCUM_ATTRS_NAME = Drop Incoming Attributes
    CONCAT_ATTRS = siteid
    GROUP_BY = org_id GetToken
    MODE = Attributes Only
    SEP = ,
    AGGREGATE -> AttributeCreator_4
AttributeCreator_4
    ATTR_TABLE = SET_TO _join = 1
    -> FeatureJoiner [RIGHT]
FeatureJoiner
    ATTR_CONFLICT_RES = Use Left
    GEOMETRY_HANDLING = Use Left
    JOIN_KEYS = _join _join AUTO
    JOIN_MODE = Inner
    JOINED -> HTTPCaller_4
HTTPCaller_4
    CONNECTION_TIMEOUT_LENGTH = 60
    CUSTOM_HEADERS = Authorization;Bearer @Value(GetToken)
    ERROR_ATTR = _error
    FILE_PATH_ATTR = _response_file_path
    FOLLOW_REDIRECTS = FOLLOW_WITH_GET
    HTTP_METHOD = POST
    MAX_HTTP_VERSION = HTTP_2
    MAX_TRANSFERS_IN_PROGRESS = 25
    OUTPUT_FILENAME = $(FME_MF_DIR)kWh.csv
    REDIRECT_AUTH = ORIGINAL_DOMAIN_ONLY
    SAVE_FILE = File
    SAVE_MULTI = No
    STATUS_CODE_ATTR = _http_status_code
    TARGET_URL = $(url)/organisations/@Value(org_id)/site-data-export
    TRANSFER_TIMEOUT_LENGTH = 90
    UPLOAD_BODY:
      {
          "assets":[@Value(siteid)]
          ,"data":
                  [{"label":"@Value(data_label)","unit":"@Value(data_unit)","source":"@Value(data_source)","type":"@Value(data_type)"}]
          ,"aggregation":"monthly"
          ,"start":"@Value(start)"
          ,"end":"@Value(end)"
      }
    UPLOAD_CONTENT_TYPE = JSON (application/json)
    UPLOAD_TYPE = Specify Upload Body
    USE_COOKIES = No
    VERIFY_SSL_CERTIFICATES = Yes
    -> Junction_5
Junction_5
    -> Junction_6

Bookmark: tokens
Creator
    GEOMTYPE = Geometry Object
    NUM = 4
    CREATED -> AttributeCreator
AttributeCreator
    ATTR_TABLE = SET_TO org_name = FME_CONDITIONAL:DEFAULT_VALUE'_FME_NO_OP_'BOOL_OP;OR;COMPOSITE_TEST;1;TEST @Value(_creation_instance) = 0'Upper Hutt City Council'BOOL_OP;OR;COMPOSITE_TEST;1;TEST @Value(_creation_instance) = 1'Hutt City Council'BOOL_OP;OR;COMPOSITE_TEST;1;TEST @Value(_creation_instance) = 2'Porirua City Council'BOOL_OP;OR;COMPOSITE_TEST;1;TEST @Value(_creation_instance) = 3'Wellington City Council'FME_NUM_CONDITIONS5___
    -> Tester
Note: PCC data not coming through for some reason
Tester
    BOOL_OP = OR
    COMPOSITE_TEST = 1
    TEST_CLAUSE = TEST @Value(org_name) != Porirua City Council
    TEST_MODE = TEST
    PASSED -> ebench_token
ebench_token: HTTPCaller
    CONNECTION_TIMEOUT_LENGTH = 60
    ERROR_ATTR = _error
    FOLLOW_REDIRECTS = FOLLOW_WITH_GET
    HTTP_METHOD = POST
    REDIRECT_AUTH = ORIGINAL_DOMAIN_ONLY
    RESPONSE_HEADER_LIST_ATTR = _headers
    SAVE_FILE = Attribute
    STATUS_CODE_ATTR = _http_status_code
    TARGET_ATTR = _response_body
    TARGET_ATTR_ENCODING = auto-detect
    TARGET_URL = $(url)/public/login/@Value(org_name)
    TRANSFER_TIMEOUT_LENGTH = 90
    UPLOAD_BODY:
      {
      	"username": "$(username)",
      	"password": "$(password)"
      }
    UPLOAD_CONTENT_TYPE = JSON (application/json)
    UPLOAD_TYPE = Specify Upload Body
    USE_COOKIES = No
    VERIFY_SSL_CERTIFICATES = Yes
    -> AttributeCreator_2
AttributeCreator_2
    ATTR_TABLE = SET_TO GetToken = @Value(_headers{2}.value)
    -> AttributeManager
AttributeManager
    ATTR_TABLE:
      REMOVE _creation_instance
      REMOVE _headers{}.name
      REMOVE _headers{}.value
      REMOVE _response_body
      REMOVE _http_status_code
    -> SQLExecutor [INITIATOR]
SQLExecutor
    COMBINE_ATTRS = Result Attributes Only
    COMBINE_GEOM = Initiator Geometry Only
    DATASET = AmazonRedshiftDW
    EXPOSED_ATTRIBUTE_LIST = alerts assetyype closed collection energy id level name org_id siteid sitename stdunit type unit name
    FORMAT = REDSHIFT
    REDSHIFT_NAMED_CONNECTION = AmazonRedshiftDW
    SQL_STATEMENT:
      WITH

      qry_orgname AS (
      	SELECT *
      	FROM "public"."eb_org_names"
      	WHERE "name" = '@Value(org_name)'
      )

      SELECT a.*, q.name
      FROM "public"."eb_assets" AS a
      INNER JOIN qry_orgname AS q
      ON a.org_id = q.org_id
    RESULT -> FeatureJoiner_2 [LEFT]
    INITIATOR -> FeatureJoiner_2 [RIGHT]
FeatureJoiner_2
    ATTR_CONFLICT_RES = Use Left
    GEOMETRY_HANDLING = Use Left
    JOIN_KEYS = name org_name AUTO
    JOIN_MODE = Inner
    JOINED -> Junction_3
Junction_3
    -> Junction_4

Bookmark: read values from csv
Junction_6
    -> FeatureHolder
FeatureHolder
    -> FeatureReader [INITIATOR]
FeatureReader
    ATTRIBUTES = CSV,"col0,1/2010,2/2010,3/2010,4/2010,5/2010,6/2010,7/2010,8/2010,9/2010,10/2010,11/2010,12/2010,1/2011,2/2011,3/2011,4/2011,5/2011,6/2011,7/2011,8/2011,9/2011,10/2011,11/2011,12/2011,1/2012,2/2012,3/2012,4/2012,5/2012,6/2012,7/2012,8/2012,9/2012,10/2012,11/2012,12/2012,1/2013,2/2013,3/2013,4/2013,5/2013,6/2013,7/2013,8/2013,9/2013,10/2013,11/2013,12/2013,1/2014,2/2014,3/2014,4/2014,5/2014,6/2014,7/2014,8/2014,9/2014,10/2014,11/2014,12/2014,1/2015,2/2015,3/2015,4/2015,5/2015,6/2015,7/2015,8/2015,9/2015,10/2015,11/2015,12/2015,1/2016,2/2016,3/2016,4/2016,5/2016,6/2016,7/2016,8/2016,9/2016,10/2016,11/2016,12/2016,1/2017,2/2017,3/2017,4/2017,5/2017,6/2017,7/2017,8/2017,9/2017,10/2017,11/2017,12/2017,1/2018,2/2018,3/2018,4/2018,5/2018,6/2018,7/2018,8/2018,9/2018,10/2018,11/2018,12/2018,1/2019,2/2019,3/2019,4/2019,5/2019,6/2019,7/2019,8/2019,9/2019,10/2019,11/2019,12/2019,1/2020,2/2020,3/2020,4/2020,5/2020,6/2020,7/2020,8/2020,9/2020,10/2020,11/2020,12/2020,1/2021,2/2021,3/2021,4/2021,5/2021,6/2021,7/2021,8/2021,9/2021"
    ATTR_ACCUM_MODE = Only Use Result
    COMBINE_GEOM = Use Result
    CSV2_CASE_SENSITIVE_FIELD_NAMES = Yes
    CSV2_CHUNK_SIZE = 100000
    CSV2_DATA_START_LINE = 4
    CSV2_DELIMITER = ,
    CSV2_ENCODING = windows-1252
    CSV2_ENFORCE_STRICT_SCHEMA = No
    CSV2_FEATURE_TYPE_NAME = FORMAT_NAME
    CSV2_FIELD_NAMES_LINE = 2
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = $(FME_MF_DIR_ENCODED)kWh.csv
    FORMAT = CSV2
    INTERACT = NONE
    OUTPUT_FEATURES_DISPLAY = Schema and Data Features
    CSV -> DuplicateFilter_2
DuplicateFilter_2
    INPUT_ORDERED_CHOICE = No
    KEYATTR = col0
    UNIQUE -> AttributeExploder
AttributeExploder
    ATTR_NAME_LABEL = _attr_name
    ATTR_VALUE_LABEL = _attr_value
    EXPLODING_TYPE = Features
    KEEP_ATTRIBUTES = Yes
    KEEP_GEOMETRY = No
    -> AttributeKeeper
AttributeKeeper
    CREATE_BULK_MODE_FEATURES = NO
    KEEP_ATTRS = _attr_name,_attr_value,col0
    -> Tester_3
Tester_3
    BOOL_OP = COMPOSITE
    COMPOSITE_TEST = 1 AND 2 AND 3
    TEST_CLAUSE:
      CASE_INSENSITIVE_TEST @Value(_attr_name) NOT_BEGINS_WITH fme
      CASE_INSENSITIVE_TEST @Value(_attr_name) NOT_BEGINS_WITH csv
      TEST @Value(_attr_name) NOT_= col0
    TEST_MODE = PER_TEST
    PASSED -> AttributeCreator_6
AttributeCreator_6
    ATTR_TABLE = SET_TO _attr_name = 1/@Value(_attr_name)
    -> DateTimeConverter
DateTimeConverter
    DATETIME_ATTR = _attr_name
    IN_FORMAT = %e/%N/%Y
    OUT_FORMAT = FME
    PASSTHROUGH = NO
    REPAIR_INPUT = YES
    -> Junction_7
Junction_7
    -> Junction_8

Bookmark: output
Junction_8
    -> AttributeManager_2
AttributeManager_2
    ATTR_TABLE:
      RENAME_SET_VALUE col0 > name
      RENAME_SET_VALUE _attr_name > datetime
      RENAME_SET_VALUE _attr_value > value
    -> DatabaseJoiner
DatabaseJoiner
    ADDED_FIELDS = siteid
    ATTR_ACCUM_MODE = Merge Joined
    ATTR_CONFLICT_RES = Use Original
    CACHE_SIZE = 5000
    DATASET = AmazonRedshiftDW
    FORMAT = REDSHIFT
    JOIN_KEYS = name sitename
    MATCH_RULE_DISPLAY = Match First (1:0..1+)
    PREFETCH_EXHAUSTIVE = Yes
    REDSHIFT_NAMED_CONNECTION = AmazonRedshiftDW
    TABLE = public.eb_assets
    JOINED -> eb_tsdata (writer REDSHIFT_1)
eb_tsdata (writer REDSHIFT_1) [off]
    attributes: siteid int8, name varchar(200), datetime timestamp, value float8
